INTERFACESTATE-MIB DEFINITIONS ::= BEGIN

-- imports and exports

IMPORTS
    MODULE-IDENTITY, OBJECT-TYPE, Integer32, Gauge32
        FROM SNMPv2-SMI
    DisplayString, TruthValue
        FROM SNMPv2-TC
    hackingExperimental
        FROM HACKING-SNMP-MIB;

InterfaceStateMIB MODULE-IDENTITY
        LAST-UPDATED    "201210150000Z"
        ORGANIZATION    "Hacking Networked Solutions Ltd"
        CONTACT-INFO    "Max Hacking"
        DESCRIPTION             "This MIB module defines objects for storpool used."
        REVISION        "201303210000Z"
        DESCRIPTION             "Derived from DISKIO-MIB ex UCD."
    ::= { InterfaceState 1 }

InterfaceState      OBJECT IDENTIFIER ::= { hackingExperimental 6 }

InterfaceStateTable OBJECT-TYPE
    SYNTAX      SEQUENCE OF SInterfaceStateEntry
    MAX-ACCESS  not-accessible
    STATUS      current
    DESCRIPTION "Table of HDD SMART information."
    ::= { InterfaceState 2 }

InterfaceStateEntry OBJECT-TYPE
    SYNTAX      SInterfaceStateEntry
    MAX-ACCESS  not-accessible
    STATUS      current
    DESCRIPTION "An entry containing a device and its statistics."
    INDEX       { InterfaceIndex }
    ::= { InterfaceStateTable 1 }

    SInterfaceStateEntry ::= SEQUENCE {
        InterfaceIndex                Integer32,
        InterfaceName         DisplayString,
        InterfaceMode         DisplayString,
        InterfaceLink         DisplayString,
        InterfaceUp         DisplayString
}

InterfaceIndex OBJECT-TYPE
    SYNTAX      Integer32 (0..65535)
    MAX-ACCESS  read-only
    STATUS      current
    DESCRIPTION "Reference index for each observed device."
    ::= { InterfaceStateEntry 1 }

InterfaceName OBJECT-TYPE
    SYNTAX      DisplayString
    MAX-ACCESS  read-only
    STATUS      current
    DESCRIPTION "Interface name"
    ::= { InterfaceStateEntry 2 }

InterfaceMode OBJECT-TYPE
    SYNTAX      DisplayString
    MAX-ACCESS  read-only
    STATUS      current
    DESCRIPTION "Interface Mode"
    ::= { InterfaceStateEntry 3 }

InterfaceLink OBJECT-TYPE
    SYNTAX      DisplayString
    MAX-ACCESS  read-only
    STATUS      current
    DESCRIPTION "Interface Mode"
    ::= { InterfaceStateEntry 4 }

InterfaceUp OBJECT-TYPE
    SYNTAX      DisplayString
    MAX-ACCESS  read-only
    STATUS      current
    DESCRIPTION "Interface Mode"
    ::= { InterfaceStateEntry 5 }

END
