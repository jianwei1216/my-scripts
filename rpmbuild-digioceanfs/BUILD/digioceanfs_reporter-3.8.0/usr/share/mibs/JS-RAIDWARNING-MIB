RAIDWARNING-MIB DEFINITIONS ::= BEGIN

-- imports and exports

IMPORTS
    MODULE-IDENTITY, OBJECT-TYPE, Integer32, Gauge32
        FROM SNMPv2-SMI
    DisplayString, TruthValue
        FROM SNMPv2-TC
    hackingExperimental
        FROM HACKING-SNMP-MIB;

RaidWarningMIB MODULE-IDENTITY
        LAST-UPDATED    "201210150000Z"
        ORGANIZATION    "Hacking Networked Solutions Ltd"
        CONTACT-INFO    "Max Hacking"
        DESCRIPTION             "This MIB module defines objects for HDD SMART data."
        REVISION        "201210150000Z"
        DESCRIPTION             "Derived from DISKIO-MIB ex UCD."
    ::= { RaidWarning 1 }

RaidWarning      OBJECT IDENTIFIER ::= { hackingExperimental 4 }

RaidWarningTable OBJECT-TYPE
    SYNTAX      SEQUENCE OF SsmartCtlEntry
    MAX-ACCESS  not-accessible
    STATUS      current
    DESCRIPTION "Table of HDD SMART information."
    ::= { RaidWarning 2 }

RaidWarningEntry OBJECT-TYPE
    SYNTAX      SsmartCtlEntry
    MAX-ACCESS  not-accessible
    STATUS      current
    DESCRIPTION "An entry containing a device and its statistics."
    INDEX       { RaidWarningRaidIndex }
    ::= { RaidWarningTable 1 }

    SRaidWarningEntry ::= SEQUENCE {
        RaidWarningRaidIndex                 Integer32,
        RaidWarningRaidName                  DisplayString,
        RaidWarningRaidPath                  DisplayString,
        RaidWarningRaidErrType               DisplayString
}

RaidWarningRaidIndex OBJECT-TYPE
    SYNTAX      Integer32
    MAX-ACCESS  read-only
    STATUS      current
    DESCRIPTION "Reference index for each observed device."
    ::= { RaidWarningEntry 1 }

RaidWarningRaidName OBJECT-TYPE
    SYNTAX      DisplayString
    MAX-ACCESS  read-only
    STATUS      current
    DESCRIPTION "Raid name"
    ::= { RaidWarningEntry 2 }

RaidWarningRaidPath OBJECT-TYPE
    SYNTAX      DisplayString
    MAX-ACCESS  read-only
    STATUS      current
    DESCRIPTION "Raid name"
    ::= { RaidWarningEntry 3 }

RaidWarningRaidErrType OBJECT-TYPE
    SYNTAX      DisplayString
    MAX-ACCESS  read-only
    STATUS      current
    DESCRIPTION "err type"
    ::= { RaidWarningEntry 4 }

END
