DISKTMEP-MIB DEFINITIONS ::= BEGIN

IMPORTS
    MODULE-IDENTITY, OBJECT-TYPE, Integer32, Gauge32
        FROM SNMPv2-SMI
    DisplayString, TruthValue
        FROM SNMPv2-TC
    hackingExperimental
        FROM HACKING-SNMP-MIB;

DiskTempMIB MODULE-IDENTITY
        LAST-UPDATED    "201307180000Z"
        ORGANIZATION    "Hacking Networked Solutions Ltd"
        CONTACT-INFO    "Max Hacking"
        DESCRIPTION             "This MIB module defines objects for HDD SMART data."
        REVISION        "201307180000Z"
        DESCRIPTION             "Derived from DISKIO-MIB ex UCD."
    ::= { DiskTemp 1 }

DiskTemp      OBJECT IDENTIFIER ::= { hackingExperimental 13 }

DiskTempTable OBJECT-TYPE
    SYNTAX      SEQUENCE OF SDiskTempEntry
    MAX-ACCESS  not-accessible
    STATUS      current
    DESCRIPTION "disk temp or add information."
    ::= { DiskTemp 2 }

DiskTempEntry OBJECT-TYPE
    SYNTAX      SDiskTemp
    MAX-ACCESS  not-accessible
    STATUS      current
    DESCRIPTION "Disk temp or add"
    INDEX       { DiskTempIndex }
    ::= { DiskTempTable 1 }

	SDiskTempEntry ::= SEQUENCE {
        DiskTempIndex                 Integer32,
	DiskTempCTime                 DisplayString,
        DiskTempDevName                  DisplayString,
        DiskTempDevTemp                  DisplayString,
        DiskTempEvent               DisplayString
}

DiskTempIndex OBJECT-TYPE
    SYNTAX      Integer32 (0..65535)
    MAX-ACCESS  read-only
    STATUS      current
    DESCRIPTION "Reference index for each observed device."
    ::= { DiskTempEntry 1 }

DiskTempCTime OBJECT-TYPE
    SYNTAX      DisplayString
    MAX-ACCESS  read-only
    STATUS      current
    DESCRIPTION "time-stamp"
    ::= { DiskTempEntry 2 }

DiskTempDevName OBJECT-TYPE
    SYNTAX      DisplayString
    MAX-ACCESS  read-only
    STATUS      current
    DESCRIPTION "disk name"
    ::= { DiskTempEntry 3 }

DiskTempDevTemp OBJECT-TYPE
    SYNTAX      DisplayString
    MAX-ACCESS  read-only
    STATUS      current
    DESCRIPTION "disk id"
    ::= { DiskTempEntry 4 }

DiskTempEvent OBJECT-TYPE
    SYNTAX      DisplayString
    MAX-ACCESS  read-only
    STATUS      current
    DESCRIPTION "Temp or add"
    ::= { DiskTempEntry 5 }

END
