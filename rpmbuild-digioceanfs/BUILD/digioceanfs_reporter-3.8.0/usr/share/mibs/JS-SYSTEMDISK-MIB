SYSTEMDISK-MIB DEFINITIONS ::= BEGIN

IMPORTS
    MODULE-IDENTITY, OBJECT-TYPE, Integer32, Gauge32
        FROM SNMPv2-SMI
    DisplayString, TruthValue
        FROM SNMPv2-TC
    hackingExperimental
        FROM HACKING-SNMP-MIB;

SystemdiskMIB MODULE-IDENTITY
        LAST-UPDATED    "201307180000Z"
        ORGANIZATION    "Perabytes Ltd"
        CONTACT-INFO    "Max Hacking"
        DESCRIPTION             "This MIB module defines objects for Fail Raid"
        REVISION        "201307180000Z"
        DESCRIPTION             "Derived from DISKIO-MIB ex UCD."
    ::= { Systemdisk 1 }

Systemdisk      OBJECT IDENTIFIER ::= { hackingExperimental 12 }

SystemdiskTable OBJECT-TYPE
    SYNTAX      SEQUENCE OF SSystemdiskEntry
    MAX-ACCESS  not-accessible
    STATUS      current
    DESCRIPTION "disk drop or add information."
    ::= { Systemdisk 2 }

SystemdiskEntry OBJECT-TYPE
    SYNTAX      SSystemdisk
    MAX-ACCESS  not-accessible
    STATUS      current
    DESCRIPTION "System disk"
    INDEX       { SystemdiskIndex }
    ::= { SystemdiskTable 1 }

	SSystemdiskEntry ::= SEQUENCE {
        SystemdiskIndex                 Integer32,
	SystemdiskCTime                  DisplayString,
        SystemdiskDir                 DisplayString,
        SystemdiskFlag                  DisplayString,
        SystemdiskUsed               DisplayString
}

SystemdiskIndex OBJECT-TYPE
    SYNTAX      Integer32 (0..65535)
    MAX-ACCESS  read-only
    STATUS      current
    DESCRIPTION "Reference index for each observed device."
    ::= { SystemdiskEntry 1 }

SystemdiskCTime OBJECT-TYPE
    SYNTAX      DisplayString
    MAX-ACCESS  read-only
    STATUS      current
    DESCRIPTION "time-stamp"
    ::= { SystemdiskEntry 2 }

SystemdiskDir OBJECT-TYPE
    SYNTAX      DisplayString
    MAX-ACCESS  read-only
    STATUS      current
    DESCRIPTION "node name"
    ::= { SystemdiskEntry 3 }

SystemdiskFlag OBJECT-TYPE
    SYNTAX      DisplayString
    MAX-ACCESS  read-only
    STATUS      current
    DESCRIPTION "ip addr"
    ::= { SystemdiskEntry 4 }

SystemdiskUsed OBJECT-TYPE
    SYNTAX      DisplayString
    MAX-ACCESS  read-only
    STATUS      current
    DESCRIPTION "event"
    ::= { SystemdiskEntry 5 }

END
