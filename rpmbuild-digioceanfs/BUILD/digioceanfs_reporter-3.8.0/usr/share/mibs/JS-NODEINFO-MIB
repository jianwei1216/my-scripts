NODEINFO-MIB DEFINITIONS ::= BEGIN

-- imports and exports

IMPORTS
    MODULE-IDENTITY, OBJECT-TYPE, Integer32, Gauge32
        FROM SNMPv2-SMI
    DisplayString, TruthValue
        FROM SNMPv2-TC
    hackingExperimental
        FROM HACKING-SNMP-MIB;

NodeInfoMIB MODULE-IDENTITY
    LAST-UPDATED    "201508140000Z" 
    ORGANIZATION    "Hacking Node Solutions Ltd"
    CONTACT-INFO    
        "Max Hacking
         DOFS Storage Management System
         Perabytes Technology Co., Ltd. Copy Right
         Website: http://www.perabytes.com
         Hot Line: 400-656-1980
        "
    DESCRIPTION     
        "This MIB module defines objects for node info."
    REVISION        "201603030000Z"
    DESCRIPTION     
        "Modify field type."
    ::= { NodeInfo 1 }

NodeInfo      OBJECT IDENTIFIER ::= { hackingExperimental 20 }

-- NodeStateTable

NodeStateTable OBJECT-TYPE
    SYNTAX      SEQUENCE OF SNodeStateEntry
    MAX-ACCESS  not-accessible
    STATUS      current
    DESCRIPTION "Table of node information."
    ::= { NodeInfo 2 }

NodeStateEntry OBJECT-TYPE
    SYNTAX      SNodeStateEntry
    MAX-ACCESS  not-accessible
    STATUS      current
    DESCRIPTION "An entry containing a node and its info."
    INDEX       { NodeStateIndex }
    ::= { NodeStateTable 1 }

    SNodeStateEntry ::= SEQUENCE {
        NodeStateIndex        Integer32,
        NodeStateName         DisplayString,
        NodeStateIP           DisplayString,
        NodeStateUp           INTEGER,
}

NodeStateIndex OBJECT-TYPE
    SYNTAX      Integer32 (0..65535)
    MAX-ACCESS  read-only
    STATUS      current
    DESCRIPTION "Reference index for each observed node."
    ::= { NodeStateEntry 1 }

NodeStateName OBJECT-TYPE
    SYNTAX      DisplayString
    MAX-ACCESS  read-only
    STATUS      current
    DESCRIPTION "Node name"
    ::= { NodeStateEntry 2 }

NodeStateIP OBJECT-TYPE
    SYNTAX      DisplayString
    MAX-ACCESS  read-only
    STATUS      current
    DESCRIPTION "IP Address of node"
    ::= { NodeStateEntry 3 }

NodeStateUp OBJECT-TYPE
    SYNTAX      INTEGER{start(1),stop(0)}
    MAX-ACCESS  read-only
    STATUS      current
    DESCRIPTION "Status of node"
    ::= { NodeStateEntry 4 }

-- NodeNicTable

NodeNicTable OBJECT-TYPE
    SYNTAX      SEQUENCE OF SNodeNicEntry
    MAX-ACCESS  not-accessible
    STATUS      current
    DESCRIPTION "Table of node Nic information."
    ::= { NodeInfo 3 }

NodeNicEntry OBJECT-TYPE
    SYNTAX      SNodeNicEntry
    MAX-ACCESS  not-accessible
    STATUS      current
    DESCRIPTION "An entry containing a device and its statistics."
    INDEX       { NodeNicIndex }
    ::= { NodeNicTable 1 }

    SNodeNicEntry ::= SEQUENCE {
        NodeNicIndex        Integer32,
        NodeNicName         DisplayString,
        NodeNicIP           DisplayString,
        NodeNicMac          DisplayString,
        NodeNicGatewa       DisplayString,
        NodeNicMask         DisplayString,
        NodeNicBroadcast    DisplayString,
        NodeNicType         DisplayString,
        NodeNicStatus       INTEGER,
}

NodeNicIndex OBJECT-TYPE
    SYNTAX      Integer32 (0..65535)
    MAX-ACCESS  read-only
    STATUS      current
    DESCRIPTION "Reference index for each observed device."
    ::= { NodeNicEntry 1 }

NodeNicName OBJECT-TYPE
    SYNTAX      DisplayString
    MAX-ACCESS  read-only
    STATUS      current
    DESCRIPTION "Nic name"
    ::= { NodeNicEntry 2 }

NodeNicIP OBJECT-TYPE
    SYNTAX      DisplayString
    MAX-ACCESS  read-only
    STATUS      current
    DESCRIPTION "IP Address of Nic"
    ::= { NodeNicEntry 3 }

NodeNicMac OBJECT-TYPE
    SYNTAX      DisplayString
    MAX-ACCESS  read-only
    STATUS      current
    DESCRIPTION "Mac Address of Nic"
    ::= { NodeNicEntry 4 }

NodeNicGateway OBJECT-TYPE
    SYNTAX      DisplayString
    MAX-ACCESS  read-only
    STATUS      current
    DESCRIPTION "Gateway of Nic"
    ::= { NodeNicEntry 5 }

NodeNicMask OBJECT-TYPE
    SYNTAX      DisplayString
    MAX-ACCESS  read-only
    STATUS      current
    DESCRIPTION "NetMaks of Nic"
    ::= { NodeNicEntry 6 }

NodeNicBroadcast OBJECT-TYPE
    SYNTAX      DisplayString
    MAX-ACCESS  read-only
    STATUS      current
    DESCRIPTION "Broadcast of Nic"
    ::= { NodeNicEntry 7 }

NodeNicType OBJECT-TYPE
    SYNTAX      DisplayString
    MAX-ACCESS  read-only
    STATUS      current
    DESCRIPTION "Type of Nic"
    ::= { NodeNicEntry 8 }

NodeNicStatus OBJECT-TYPE
    SYNTAX      INTEGER{no(0),yes(1)}
    MAX-ACCESS  read-only
    STATUS      current
    DESCRIPTION "Nic status"
    ::= { NodeNicEntry 9 }

-- NodeRaidTable

NodeDiskTable OBJECT-TYPE
    SYNTAX      SEQUENCE OF SNodeDiskEntry
    MAX-ACCESS  not-accessible
    STATUS      current
    DESCRIPTION "Table of node disk information."
    ::= { NodeInfo 4 }

NodeDiskEntry OBJECT-TYPE
    SYNTAX      SNodeDiskEntry
    MAX-ACCESS  not-accessible
    STATUS      current
    DESCRIPTION "An entry containing a device and its statistics."
    INDEX       { NodeDiskIndex }
    ::= { NodeDiskTable 1 }

    SNodeDiskEntry ::= SEQUENCE {
        NodeDiskIndex        Integer32,
        NodeDiskName         DisplayString,
        NodeDiskStatus       DisplayString,
        NodeDiskSize         Gauge32,
        NodeDiskSN           DisplayString,
        NodeDiskVandor       DisplayString,
        NodeDiskType         DisplayString,
        NodeDiskPosition     DisplayString,
        NodeDiskIstart       INTEGER,
        NodeDiskPort         Integer32,
        NodeDiskService      DisplayString,
        NodeDiskPid          Integer32,
}

NodeDiskIndex OBJECT-TYPE
    SYNTAX      Integer32 (0..65535)
    MAX-ACCESS  read-only
    STATUS      current
    DESCRIPTION "Reference index for each observed device."
    ::= { NodeDiskEntry 1 }

NodeDiskName OBJECT-TYPE
    SYNTAX      DisplayString
    MAX-ACCESS  read-only
    STATUS      current
    DESCRIPTION "Disk name"
    ::= { NodeDiskEntry 2 }

NodeDiskStatus OBJECT-TYPE
    SYNTAX      DisplayString
    MAX-ACCESS  read-only
    STATUS      current
    DESCRIPTION "Disk Status"
    ::= { NodeDiskEntry 3 }

NodeDiskSize OBJECT-TYPE
    SYNTAX      Gauge32
    MAX-ACCESS  read-only
    STATUS      current
    DESCRIPTION "Disk Size"
    ::= { NodeDiskEntry 4 }

NodeDiskSN OBJECT-TYPE
    SYNTAX      DisplayString
    MAX-ACCESS  read-only
    STATUS      current
    DESCRIPTION "Disk Serial Number"
    ::= { NodeDiskEntry 5 }

NodeDiskVandor OBJECT-TYPE
    SYNTAX      DisplayString
    MAX-ACCESS  read-only
    STATUS      current
    DESCRIPTION "Disk Model"
    ::= { NodeDiskEntry 6 }

NodeDiskType OBJECT-TYPE
    SYNTAX      DisplayString
    MAX-ACCESS  read-only
    STATUS      current
    DESCRIPTION "Disk Type"
    ::= { NodeDiskEntry 7 }

NodeDiskPosition OBJECT-TYPE
    SYNTAX      DisplayString
    MAX-ACCESS  read-only
    STATUS      current
    DESCRIPTION "Disk Position"
    ::= { NodeDiskEntry 8 }

NodeDiskIstart OBJECT-TYPE
    SYNTAX      INTEGER{start(1),stop(0),nostate(-1)}
    MAX-ACCESS  read-only
    STATUS      current
    DESCRIPTION "The service(disk belongs) status"
    ::= { NodeDiskEntry 9 }

NodeDiskPort OBJECT-TYPE
    SYNTAX      Integer32(0..65535)
    MAX-ACCESS  read-only
    STATUS      current
    DESCRIPTION "Disk Port"
    ::= { NodeDiskEntry 10 }

NodeDiskService OBJECT-TYPE
    SYNTAX      DisplayString
    MAX-ACCESS  read-only
    STATUS      current
    DESCRIPTION "Service(disk belongs) name"
    ::= { NodeDiskEntry 11 }

NodeDiskPid OBJECT-TYPE
    SYNTAX      Integer32(0..32768)
    MAX-ACCESS  read-only
    STATUS      current
    DESCRIPTION "Disk Pid"
    ::= { NodeDiskEntry 12 }

-- NodeRaidTable

NodeRaidTable OBJECT-TYPE
    SYNTAX      SEQUENCE OF SNodeRaidEntry
    MAX-ACCESS  not-accessible
    STATUS      current
    DESCRIPTION "Table of node raid information."
    ::= { NodeInfo 5 }

NodeRaidEntry OBJECT-TYPE
    SYNTAX      SNodeRaidEntry
    MAX-ACCESS  not-accessible
    STATUS      current
    DESCRIPTION "An entry containing a device and its statistics."
    INDEX       { NodeRaidIndex }
    ::= { NodeRaidTable 1 }

    SNodeRaidEntry ::= SEQUENCE {
        NodeRaidIndex        Integer32,
        NodeRaidName         DisplayString,
        NodeRaidStatus       DisplayString,
        NodeRaidSize         Gauge32,
        NodeRaidActive       INTEGER,
        NodeRaidVandor       DisplayString,
        NodeRaidDevs         DisplayString,
        NodeRaidIstart       INTEGER,
        NodeRaidPort         Integer32,
        NodeRaidService      DisplayString,
        NodeRaidPid          Integer32,
}

NodeRaidIndex OBJECT-TYPE
    SYNTAX      Integer32 (0..65535)
    MAX-ACCESS  read-only
    STATUS      current
    DESCRIPTION "Reference index for each observed device."
    ::= { NodeRaidEntry 1 }

NodeRaidName OBJECT-TYPE
    SYNTAX      DisplayString
    MAX-ACCESS  read-only
    STATUS      current
    DESCRIPTION "Raid Name"
    ::= { NodeRaidEntry 2 }

NodeRaidStatus OBJECT-TYPE
    SYNTAX      DisplayString
    MAX-ACCESS  read-only
    STATUS      current
    DESCRIPTION "Raid Status"
    ::= { NodeRaidEntry 3 }

NodeRaidSize OBJECT-TYPE
    SYNTAX      Gauge32
    MAX-ACCESS  read-only
    STATUS      current
    DESCRIPTION "Raid Size"
    ::= { NodeRaidEntry 4 }

NodeRaidActive OBJECT-TYPE
    SYNTAX      INTEGER{active(1),inactive(0)}
    MAX-ACCESS  read-only
    STATUS      current
    DESCRIPTION "Raid Active or Not"
    ::= { NodeRaidEntry 5 }

NodeRaidVandor OBJECT-TYPE
    SYNTAX      DisplayString
    MAX-ACCESS  read-only
    STATUS      current
    DESCRIPTION "Raid level"
    ::= { NodeRaidEntry 6 }

NodeRaidDevs OBJECT-TYPE
    SYNTAX      DisplayString
    MAX-ACCESS  read-only
    STATUS      current
    DESCRIPTION "Disks in Raid"
    ::= { NodeRaidEntry 7 }

NodeRaidIstart OBJECT-TYPE
    SYNTAX      INTEGER{start(1),stop(0),nostate(-1)}
    MAX-ACCESS  read-only
    STATUS      current
    DESCRIPTION "Service(raid belongs) Status"
    ::= { NodeRaidEntry 8 }

NodeRaidPort OBJECT-TYPE
    SYNTAX      Integer32(0..65535)
    MAX-ACCESS  read-only
    STATUS      current
    DESCRIPTION "Raid Port"
    ::= { NodeRaidEntry 9 }

NodeRaidService OBJECT-TYPE
    SYNTAX      DisplayString
    MAX-ACCESS  read-only
    STATUS      current
    DESCRIPTION "Service(raid belongs) Name"
    ::= { NodeRaidEntry 10 }

NodeRaidPid OBJECT-TYPE
    SYNTAX      Integer32(0..32768)
    MAX-ACCESS  read-only
    STATUS      current
    DESCRIPTION "Raid Pid"
    ::= { NodeRaidEntry 11 }

-- NodeSysTable

NodeSysTable OBJECT-TYPE
    SYNTAX      SEQUENCE OF SNodeRaidEntry
    MAX-ACCESS  not-accessible
    STATUS      current
    DESCRIPTION "Table of node system information."
    ::= { NodeInfo 6 }

NodeSysEntry      OBJECT IDENTIFIER ::= { NodeSysTable 1 }

NodeSysVitalsEntry OBJECT-TYPE
    SYNTAX      SNodeSysVitalsEntry
    MAX-ACCESS  not-accessible
    STATUS      current
    DESCRIPTION "An entry containing a vitals device and its statistics."
    INDEX       { NodeSysVitalsIndex }
    ::= { NodeSysEntry 1 }

    SNodeSysVitalsEntry ::= SEQUENCE {
        NodeSysVitalsIndex        Integer32,
        NodeSysVitalsDistro       DisplayString,
        NodeSysVitalsHostname     DisplayString,
        NodeSysVitalsIPAddr       DisplayString,
        NodeSysVitalsKernel       DisplayString,
        NodeSysVitalsLoadAvg      DisplayString,
        NodeSysVitalsUptime       DisplayString,
        NodeSysVitalsUsers        Integer32,
}

NodeSysVitalsIndex OBJECT-TYPE
    SYNTAX      Integer32 (0..65535)
    MAX-ACCESS  read-only
    STATUS      current
    DESCRIPTION "Reference index for each observed device."
    ::= { NodeSysVitalsEntry 1 }

NodeSysVitalsDistro OBJECT-TYPE
    SYNTAX      DisplayString
    MAX-ACCESS  read-only
    STATUS      current
    DESCRIPTION "Release of the system"
    ::= { NodeSysVitalsEntry 2 }

NodeSysVitalsHostname OBJECT-TYPE
    SYNTAX      DisplayString
    MAX-ACCESS  read-only
    STATUS      current
    DESCRIPTION "Hostname"
    ::= { NodeSysVitalsEntry 3 }

NodeSysVitalsIPAddr OBJECT-TYPE
    SYNTAX      DisplayString
    MAX-ACCESS  read-only
    STATUS      current
    DESCRIPTION "IP Address"
    ::= { NodeSysVitalsEntry 4 }

NodeSysVitalsKernel OBJECT-TYPE
    SYNTAX      DisplayString
    MAX-ACCESS  read-only
    STATUS      current
    DESCRIPTION "Kernel Version"
    ::= { NodeSysVitalsEntry 5 }

NodeSysVitalsLoadAvg OBJECT-TYPE
    SYNTAX      DisplayString
    MAX-ACCESS  read-only
    STATUS      current
    DESCRIPTION "Average Load"
    ::= { NodeSysVitalsEntry 6 }

NodeSysVitalsUptime OBJECT-TYPE
    SYNTAX      DisplayString
    MAX-ACCESS  read-only
    STATUS      current
    DESCRIPTION "The last startup time"
    ::= { NodeSysVitalsEntry 7 }

NodeSysVitalsUsers OBJECT-TYPE
    SYNTAX      Integer32(0..65535)
    MAX-ACCESS  read-only
    STATUS      current
    DESCRIPTION "The Number of login user"
    ::= { NodeSysVitalsEntry 8 }

NodeSysNetEntry OBJECT-TYPE
    SYNTAX      SNodeSysNetEntry
    MAX-ACCESS  not-accessible
    STATUS      current
    DESCRIPTION "An entry containing a net device and its statistics."
    INDEX       { NodeSysNetIndex }
    ::= { NodeSysEntry 2 }

    SNodeSysNetEntry ::= SEQUENCE {
        NodeSysNetIndex        Integer32,
        NodeSysNetName         DisplayString,
        NodeSysNetErrors       Gauge32,
        NodeSysNetDrops        Gauge32,
        NodeSysNetRxBytes      Gauge32,
        NodeSysNetTxBytes      Gauge32,
}

NodeSysNetIndex OBJECT-TYPE
    SYNTAX      Integer32 (0..65535)
    MAX-ACCESS  read-only
    STATUS      current
    DESCRIPTION "Reference index for each observed device."
    ::= { NodeSysNetEntry 1 }

NodeSysNetName OBJECT-TYPE
    SYNTAX      DisplayString
    MAX-ACCESS  read-only
    STATUS      current
    DESCRIPTION "Net Name"
    ::= { NodeSysNetEntry 2 }

NodeSysNetErrors OBJECT-TYPE
    SYNTAX      Gauge32
    MAX-ACCESS  read-only
    STATUS      current
    DESCRIPTION "Error Packets"
    ::= { NodeSysNetEntry 3 }

NodeSysNetDrops OBJECT-TYPE
    SYNTAX      Gauge32
    MAX-ACCESS  read-only
    STATUS      current
    DESCRIPTION "Drop Packets"
    ::= { NodeSysNetEntry 4 }

NodeSysNetRxBytes OBJECT-TYPE
    SYNTAX      Gauge32
    MAX-ACCESS  read-only
    STATUS      current
    DESCRIPTION "Bytes Received"
    ::= { NodeSysNetEntry 5 }

NodeSysNetTxBytes OBJECT-TYPE
    SYNTAX      Gauge32
    MAX-ACCESS  read-only
    STATUS      current
    DESCRIPTION "Bytes Transfered "
    ::= { NodeSysNetEntry 6 }

NodeSysMemEntry OBJECT-TYPE
    SYNTAX      SNodeSysMemEntry
    MAX-ACCESS  not-accessible
    STATUS      current
    DESCRIPTION "An entry containing a memory device and its statistics."
    INDEX       { NodeSysMemIndex }
    ::= { NodeSysEntry 3 }

    SNodeSysMemEntry ::= SEQUENCE {
        NodeSysMemIndex           Integer32,
        NodeSysMemFree            Gauge32,
        NodeSysMemPercent         Integer32,
        NodeSysMemTotal           Gauge32,
        NodeSysMemUsed            Gauge32,
        NodeSysMemApp             Gauge32,
        NodeSysMemAppPercent      Integer32,
        NodeSysMemBuffers         Gauge32,
        NodeSysMemBuffersPercent  Integer32,
        NodeSysMemCached          Gauge32,
        NodeSysMemCachedPercent   Integer32,
}

NodeSysMemIndex OBJECT-TYPE
    SYNTAX      Integer32 (0..65535)
    MAX-ACCESS  read-only
    STATUS      current
    DESCRIPTION "Reference index for each observed device."
    ::= { NodeSysMemEntry 1 }

NodeSysMemFree OBJECT-TYPE
    SYNTAX      Gauge32
    MAX-ACCESS  read-only
    STATUS      current
    DESCRIPTION "Free Size of Memory"
    ::= { NodeSysMemEntry 2 }

NodeSysMemPercent OBJECT-TYPE
    SYNTAX      Integer32(0..100)
    MAX-ACCESS  read-only
    STATUS      current
    DESCRIPTION "Memory Usage"
    ::= { NodeSysMemEntry 3 }

NodeSysMemTotal OBJECT-TYPE
    SYNTAX      Gauge32
    MAX-ACCESS  read-only
    STATUS      current
    DESCRIPTION "Total Size of Memory"
    ::= { NodeSysMemEntry 4 }

NodeSysMemUsed OBJECT-TYPE
    SYNTAX      Gauge32
    MAX-ACCESS  read-only
    STATUS      current
    DESCRIPTION "Used Size of Memory"
    ::= { NodeSysMemEntry 5 }

NodeSysMemApp OBJECT-TYPE
    SYNTAX      Gauge32
    MAX-ACCESS  read-only
    STATUS      current
    DESCRIPTION "App of Memory"
    ::= { NodeSysMemEntry 6 }

NodeSysMemAppPercent OBJECT-TYPE
    SYNTAX      Integer32(0..100)
    MAX-ACCESS  read-only
    STATUS      current
    DESCRIPTION "App of Memory Usage"
    ::= { NodeSysMemEntry 7 }

NodeSysMemBuffers OBJECT-TYPE
    SYNTAX      Gauge32
    MAX-ACCESS  read-only
    STATUS      current
    DESCRIPTION "Buffers of Memory"
    ::= { NodeSysMemEntry 8 }

NodeSysMemBuffersPercent OBJECT-TYPE
    SYNTAX      Integer32(0..100)
    MAX-ACCESS  read-only
    STATUS      current
    DESCRIPTION "Buffers of Memory Usage"
    ::= { NodeSysMemEntry 9 }

NodeSysMemCached OBJECT-TYPE
    SYNTAX      Gauge32
    MAX-ACCESS  read-only
    STATUS      current
    DESCRIPTION "Cached of Memory"
    ::= { NodeSysMemEntry 10 }

NodeSysMemCachedPercent OBJECT-TYPE
    SYNTAX      Integer32(0..100)
    MAX-ACCESS  read-only
    STATUS      current
    DESCRIPTION "Cached of Memory"
    ::= { NodeSysMemEntry 11 }

NodeSysMountEntry OBJECT-TYPE
    SYNTAX      SNodeSysMountEntry
    MAX-ACCESS  not-accessible
    STATUS      current
    DESCRIPTION "An entry containing a mount device and its statistics."
    INDEX       { NodeSysMountIndex }
    ::= { NodeSysEntry 4 }

    SNodeSysMountEntry ::= SEQUENCE {
        NodeSysMountIndex        Integer32,
        NodeSysMountFree         Gauge32,
        NodeSysMountMountPoint   DisplayString,
        NodeSysMountPercent      Integer32,
        NodeSysMountTotal        Gauge32,
        NodeSysMountUsed         Gauge32,
}

NodeSysMountIndex OBJECT-TYPE
    SYNTAX      Integer32 (0..65535)
    MAX-ACCESS  read-only
    STATUS      current
    DESCRIPTION "Reference index for each observed device."
    ::= { NodeSysMountEntry 1 }

NodeSysMountFree OBJECT-TYPE
    SYNTAX      Gauge32
    MAX-ACCESS  read-only
    STATUS      current
    DESCRIPTION "Free Size of Disk"
    ::= { NodeSysMountEntry 2 }

NodeSysMountMountPoint OBJECT-TYPE
    SYNTAX      DisplayString
    MAX-ACCESS  read-only
    STATUS      current
    DESCRIPTION "The Mount Point of Disk"
    ::= { NodeSysMountEntry 3 }

NodeSysMountPercent OBJECT-TYPE
    SYNTAX      Integer32(0..100)
    MAX-ACCESS  read-only
    STATUS      current
    DESCRIPTION " Usage of Disk"
    ::= { NodeSysMountEntry 4 }

NodeSysMountTotal OBJECT-TYPE
    SYNTAX      Gauge32
    MAX-ACCESS  read-only
    STATUS      current
    DESCRIPTION "Total Size of Disk"
    ::= { NodeSysMountEntry 5 }

NodeSysMountUsed OBJECT-TYPE
    SYNTAX      Gauge32
    MAX-ACCESS  read-only
    STATUS      current
    DESCRIPTION "Used Size of Disk"
    ::= { NodeSysMountEntry 6 }

-- NodeDiskSmartTable

NodeDiskSmartTable OBJECT-TYPE
    SYNTAX      SEQUENCE OF SNodeDiskSmartEntry
    MAX-ACCESS  not-accessible
    STATUS      current
    DESCRIPTION "Table of node Smart information."
    ::= { NodeInfo 7 }

NodeDiskSmartEntry OBJECT-TYPE
    SYNTAX      SNodeDiskSmartEntry
    MAX-ACCESS  not-accessible
    STATUS      current
    DESCRIPTION "An entry containing a device and its statistics."
    INDEX       { NodeDiskSmartIndex }
    ::= { NodeDiskSmartTable 1 }

    SNodeDiskSmartEntry ::= SEQUENCE {
        NodeDiskSmartIndex             Integer32,
        NodeDiskSmartName              DisplayString,
        NodeDiskSmartSN                DisplayString,
        NodeDiskSmartStatus            INTEGER,
        NodeDiskSmartHealth            INTEGER,
        NodeDiskSmartExecutionStatus   DisplayString,
        NodeDiskSmartAttrID            Gauge32,
        NodeDiskSmartAttrName          DisplayString,
        NodeDiskSmartAttrValue         Gauge32,
        NodeDiskSmartAttrWorst         Gauge32,
        NodeDiskSmartAttrThresh        Gauge32,
        NodeDiskSmartAttrWhenFailed    DisplayString,
        NodeDiskSmartAttrRawValue      Gauge32,
        NodeDiskSmartAttrStatus        DisplayString,
}

NodeDiskSmartIndex OBJECT-TYPE
    SYNTAX      Integer32 (0..65535)
    MAX-ACCESS  read-only
    STATUS      current
    DESCRIPTION "Reference index for each observed device."
    ::= { NodeDiskSmartEntry 1 }

NodeDiskSmartName OBJECT-TYPE
    SYNTAX      DisplayString
    MAX-ACCESS  read-only
    STATUS      current
    DESCRIPTION "Disk Name"
    ::= { NodeDiskSmartEntry 2 }

NodeDiskSmartSN OBJECT-TYPE
    SYNTAX      DisplayString
    MAX-ACCESS  read-only
    STATUS      current
    DESCRIPTION "Disk Serial Number"
    ::= { NodeDiskSmartEntry 3 }

NodeDiskSmartStatus OBJECT-TYPE
    SYNTAX      INTEGER{enabled(1),disabled(0)}
    MAX-ACCESS  read-only
    STATUS      current
    DESCRIPTION "S.M.A.R.T Status"
    ::= { NodeDiskSmartEntry 4 }

NodeDiskSmartHealth OBJECT-TYPE
    SYNTAX      INTEGER{true(1),false(0)}
    MAX-ACCESS  read-only
    STATUS      current
    DESCRIPTION "SMART Overall-health Self-assessment Test Result"
    ::= { NodeDiskSmartEntry 5 }

NodeDiskSmartExecutionStatus OBJECT-TYPE
    SYNTAX      DisplayString
    MAX-ACCESS  read-only
    STATUS      current
    DESCRIPTION "Self-test Execution Status"
    ::= { NodeDiskSmartEntry 6 }

NodeDiskSmartAttrID OBJECT-TYPE
    SYNTAX      Gauge32
    MAX-ACCESS  read-only
    STATUS      current
    DESCRIPTION "Smart Attribute ID"
    ::= { NodeDiskSmartEntry 7 }

NodeDiskSmartAttrName OBJECT-TYPE
    SYNTAX      DisplayString
    MAX-ACCESS  read-only
    STATUS      current
    DESCRIPTION "Smart Attribute Name  "
    ::= { NodeDiskSmartEntry 8 }

NodeDiskSmartAttrValue OBJECT-TYPE
    SYNTAX      Gauge32
    MAX-ACCESS  read-only
    STATUS      current
    DESCRIPTION "Smart Attribute Value"
    ::= { NodeDiskSmartEntry 9 }

NodeDiskSmartAttrWorst OBJECT-TYPE
    SYNTAX      Gauge32
    MAX-ACCESS  read-only
    STATUS      current
    DESCRIPTION "Smart Attribute Worst Value"
    ::= { NodeDiskSmartEntry 10 }

NodeDiskSmartAttrThresh OBJECT-TYPE
    SYNTAX      Gauge32
    MAX-ACCESS  read-only
    STATUS      current
    DESCRIPTION "Smart Attribute Thresh "
    ::= { NodeDiskSmartEntry 11 }

NodeDiskSmartAttrWhenFailed OBJECT-TYPE
    SYNTAX      DisplayString
    MAX-ACCESS  read-only
    STATUS      current
    DESCRIPTION "Smart Attribute When Failed"
    ::= { NodeDiskSmartEntry 12 }

NodeDiskSmartAttrRawValue OBJECT-TYPE
    SYNTAX      Gauge32
    MAX-ACCESS  read-only
    STATUS      current
    DESCRIPTION "Smart Attribute Raw Value"
    ::= { NodeDiskSmartEntry 13 }

NodeDiskSmartAttrStatus OBJECT-TYPE
    SYNTAX      DisplayString
    MAX-ACCESS  read-only
    STATUS      current
    DESCRIPTION "Smart Attribute Status"
    ::= { NodeDiskSmartEntry 14 }

-- NodeInactiveTable

NodeInactiveTable OBJECT-TYPE
    SYNTAX      SEQUENCE OF SNodeInactiveEntry
    MAX-ACCESS  not-accessible
    STATUS      current
    DESCRIPTION "Table of node inactive disk information."
    ::= { NodeInfo 8 }

NodeInactiveEntry OBJECT-TYPE
    SYNTAX      SNodeInactiveEntry
    MAX-ACCESS  not-accessible
    STATUS      current
    DESCRIPTION "An entry containing a device and its statistics."
    INDEX       { NodeInactiveIndex }
    ::= { NodeInactiveTable 1 }

    SNodeInactiveEntry ::= SEQUENCE {
        NodeInactiveIndex         Integer32,
        NodeInactiveRaidname      DisplayString,
        NodeInactiveRaidUuid      DisplayString,
        NodeInactiveNormalCount   Gauge32,
        NodeInactiveDiskNum       Gauge32,
        NodeInactiveChildName     DisplayString,
        NodeInactiveChildType     DisplayString,
}

NodeInactiveIndex OBJECT-TYPE
    SYNTAX      Integer32 (0..65535)
    MAX-ACCESS  read-only
    STATUS      current
    DESCRIPTION "Reference index for each observed device."
    ::= { NodeInactiveEntry 1 }

NodeInactiveRaidname OBJECT-TYPE
    SYNTAX      DisplayString
    MAX-ACCESS  read-only
    STATUS      current
    DESCRIPTION "Raid Name"
    ::= { NodeInactiveEntry 2 }

NodeInactiveRaidUuid OBJECT-TYPE
    SYNTAX      DisplayString
    MAX-ACCESS  read-only
    STATUS      current
    DESCRIPTION "Raid UUID"
    ::= { NodeInactiveEntry 3 }

NodeInactiveNormalCount OBJECT-TYPE
    SYNTAX      Gauge32
    MAX-ACCESS  read-only
    STATUS      current
    DESCRIPTION "The number of normal disk in raid"
    ::= { NodeInactiveEntry 4 }

NodeInactiveDiskNum OBJECT-TYPE
    SYNTAX      Gauge32
    MAX-ACCESS  read-only
    STATUS      current
    DESCRIPTION "The number of break disk in raid"
    ::= { NodeInactiveEntry 5 }

NodeInactiveChildName OBJECT-TYPE
    SYNTAX      DisplayString
    MAX-ACCESS  read-only
    STATUS      current
    DESCRIPTION "The name of break disk "
    ::= { NodeInactiveEntry 6 }

NodeInactiveChildType OBJECT-TYPE
    SYNTAX      DisplayString
    MAX-ACCESS  read-only
    STATUS      current
    DESCRIPTION "The type of break disk in raid"
    ::= { NodeInactiveEntry 7 }

-- NodeNFSStatusTable

NodeNFSStatusTable OBJECT-TYPE
    SYNTAX      SEQUENCE OF SNodeNFSStatusEntry
    MAX-ACCESS  not-accessible
    STATUS      current
    DESCRIPTION "Table of node NFS information."
    ::= { NodeInfo 9 }

NodeNFSStatusEntry OBJECT-TYPE
    SYNTAX      SNodeNFSStatusEntry
    MAX-ACCESS  not-accessible
    STATUS      current
    DESCRIPTION "An entry containing a device and its statistics."
    INDEX       { NodeNFSStatusIndex }
    ::= { NodeNFSStatusTable 1 }

    SNodeNFSStatusEntry ::= SEQUENCE {
        NodeNFSStatusIndex    Integer32,
        NodeNFSStatusName     DisplayString,
        NodeNFSStatusUp       INTEGER,
}

NodeNFSStatusIndex OBJECT-TYPE
    SYNTAX      Integer32 (0..65535)
    MAX-ACCESS  read-only
    STATUS      current
    DESCRIPTION "Reference index for each observed device."
    ::= { NodeNFSStatusEntry 1 }

NodeNFSStatusName OBJECT-TYPE
    SYNTAX      DisplayString
    MAX-ACCESS  read-only
    STATUS      current
    DESCRIPTION "Node Name"
    ::= { NodeNFSStatusEntry 2 }

NodeNFSStatusUp OBJECT-TYPE
    SYNTAX      INTEGER{start(1),stop(0)}
    MAX-ACCESS  read-only
    STATUS      current
    DESCRIPTION "NFS Status"
    ::= { NodeNFSStatusEntry 3 }

-- NodeCIFSStatusTable

NodeCIFSStatusTable OBJECT-TYPE
    SYNTAX      SEQUENCE OF SNodeCIFSStatusEntry
    MAX-ACCESS  not-accessible
    STATUS      current
    DESCRIPTION "Table of node CIFS information."
    ::= { NodeInfo 10 }

NodeCIFSStatusEntry OBJECT-TYPE
    SYNTAX      SNodeCIFSStatusEntry
    MAX-ACCESS  not-accessible
    STATUS      current
    DESCRIPTION "An entry containing a device and its statistics."
    INDEX       { NodeCIFSStatusIndex }
    ::= { NodeCIFSStatusTable 1 }

    SNodeCIFSStatusEntry ::= SEQUENCE {
        NodeCIFSStatusIndex    Integer32,
        NodeCIFSStatusName     DisplayString,
        NodeCIFSStatusUp       INTEGER,
}

NodeCIFSStatusIndex OBJECT-TYPE
    SYNTAX      Integer32 (0..65535)
    MAX-ACCESS  read-only
    STATUS      current
    DESCRIPTION "Reference index for each observed device."
    ::= { NodeCIFSStatusEntry 1 }

NodeCIFSStatusName OBJECT-TYPE
    SYNTAX      DisplayString
    MAX-ACCESS  read-only
    STATUS      current
    DESCRIPTION "Node name"
    ::= { NodeCIFSStatusEntry 2 }

NodeCIFSStatusUp OBJECT-TYPE
    SYNTAX      INTEGER{start(1),stop(0)}
    MAX-ACCESS  read-only
    STATUS      current
    DESCRIPTION "CIFS Status"
    ::= { NodeCIFSStatusEntry 3 }

-- NodeDeviceIDTable

NodeDeviceIDTable OBJECT-TYPE
    SYNTAX      SEQUENCE OF SNodeDeviceIDEntry
    MAX-ACCESS  not-accessible
    STATUS      current
    DESCRIPTION "Table of node device id information."
    ::= { NodeInfo 11 }

NodeDeviceIDEntry OBJECT-TYPE
    SYNTAX      SNodeDeviceIDEntry
    MAX-ACCESS  not-accessible
    STATUS      current
    DESCRIPTION "An entry containing a device and its statistics."
    ::= { NodeDeviceIDTable 1 }

    SNodeDeviceIDEntry ::= SEQUENCE {
        NodeDeviceIDNodeName    DisplayString,
        NodeDeviceIDRegId       DisplayString,
        NodeDeviceIDLicense     DisplayString,
}

NodeDeviceIDNodeName OBJECT-TYPE
    SYNTAX      DisplayString
    MAX-ACCESS  read-only
    STATUS      current
    DESCRIPTION "Node Name"
    ::= { NodeDeviceIDEntry 1 }

NodeDeviceIDRegId OBJECT-TYPE
    SYNTAX      DisplayString
    MAX-ACCESS  read-only
    STATUS      current
    DESCRIPTION "Registration ID"
    ::= { NodeDeviceIDEntry 2 }

NodeDeviceIDLicense OBJECT-TYPE
    SYNTAX      DisplayString
    MAX-ACCESS  read-only
    STATUS      current
    DESCRIPTION "License"
    ::= { NodeDeviceIDEntry 3 }

-- NodeCpuTable

NodeCpuTable OBJECT-TYPE
    SYNTAX      SEQUENCE OF SNodeCpuEntry
    MAX-ACCESS  not-accessible
    STATUS      current
    DESCRIPTION "Table of node CPU information."
    ::= { NodeInfo 12 }

NodeCpuEntry OBJECT-TYPE
    SYNTAX      SNodeCpuEntry
    MAX-ACCESS  not-accessible
    STATUS      current
    DESCRIPTION "An entry containing a device and its statistics."
    ::= { NodeCpuTable 1 }

    SNodeCpuEntry ::= SEQUENCE {
        NodeCpuNodeName        DisplayString,
        NodeCpuProcessorTotal  Gauge32,
        NodeCpuInfo            DisplayString,
}

NodeCpuNodeName OBJECT-TYPE
    SYNTAX      DisplayString
    MAX-ACCESS  read-only
    STATUS      current
    DESCRIPTION "Node Name"
    ::= { NodeCpuEntry 1 }

NodeCpuProcessorTotal OBJECT-TYPE
    SYNTAX      Gauge32
    MAX-ACCESS  read-only
    STATUS      current
    DESCRIPTION "Total of CPU Processor"
    ::= { NodeCpuEntry 2 }

NodeCpuInfo OBJECT-TYPE
    SYNTAX      DisplayString
    MAX-ACCESS  read-only
    STATUS      current
    DESCRIPTION "CPU Info"
    ::= { NodeCpuEntry 3 }

-- NodeSmsTable

NodeSmsTable OBJECT-TYPE
    SYNTAX      SEQUENCE OF SNodeSmsEntry
    MAX-ACCESS  not-accessible
    STATUS      current
    DESCRIPTION "Table of node SMS Warning information."
    ::= { NodeInfo 13 }

NodeSmsEntry OBJECT-TYPE
    SYNTAX      SNodeSmsEntry
    MAX-ACCESS  not-accessible
    STATUS      current
    DESCRIPTION "An entry containing a device and its statistics."
    ::= { NodeSmsTable 1 }

    SNodeSmsEntry ::= SEQUENCE {
        NodeSmsInuse          INTEGER,
        NodeSmsWarningType    DisplayString,
        NodeSmsCenterNumber   DisplayString,
        NodeSmsMobilePhone    DisplayString,
}

NodeSmsInuse OBJECT-TYPE
    SYNTAX      INTEGER{true(1),false(0)}
    MAX-ACCESS  read-only
    STATUS      current
    DESCRIPTION "SMS Status"
    ::= { NodeSmsEntry 1 }

NodeSmsWarningType OBJECT-TYPE
    SYNTAX      DisplayString
    MAX-ACCESS  read-only
    STATUS      current
    DESCRIPTION "Type of Warning"
    ::= { NodeSmsEntry 2 }

NodeSmsCenterNumber OBJECT-TYPE
    SYNTAX      DisplayString
    MAX-ACCESS  read-only
    STATUS      current
    DESCRIPTION "SMS Center Number"
    ::= { NodeSmsEntry 3 }

NodeSmsMobilePhone OBJECT-TYPE
    SYNTAX      DisplayString
    MAX-ACCESS  read-only
    STATUS      current
    DESCRIPTION "SMS Receiving Number"
    ::= { NodeSmsEntry 4 }

-- NodeIPMITable

NodeIPMITable OBJECT-TYPE
    SYNTAX      SEQUENCE OF SNodeIPMIEntry
    MAX-ACCESS  not-accessible
    STATUS      current
    DESCRIPTION "Table of node IPMI information."
    ::= { NodeInfo 14 }

NodeIPMIEntry OBJECT-TYPE
    SYNTAX      SNodeIPMIEntry
    MAX-ACCESS  not-accessible
    STATUS      current
    DESCRIPTION "An entry containing a device and its statistics."
    ::= { NodeIPMITable 1 }

    SNodeIPMIEntry ::= SEQUENCE {
        NodeIPMIPowerStatus   INTEGER,
        NodeIPMIIPSource      DisplayString,
        NodeIPMIIpAddress     DisplayString,
        NodeIPMINetMask       DisplayString,
        NodeIPMIGateway       DisplayString,
}

NodeIPMIPowerStatus OBJECT-TYPE
    SYNTAX      INTEGER{on(1),off(0)}
    MAX-ACCESS  read-only
    STATUS      current
    DESCRIPTION "Node Status"
    ::= { NodeIPMIEntry 1 }

NodeIPMIIPSource OBJECT-TYPE
    SYNTAX      DisplayString
    MAX-ACCESS  read-only
    STATUS      current
    DESCRIPTION "IPMI IP Source"
    ::= { NodeIPMIEntry 2 }

NodeIPMIIpAddress OBJECT-TYPE
    SYNTAX      DisplayString
    MAX-ACCESS  read-only
    STATUS      current
    DESCRIPTION "IPMI IP Address"
    ::= { NodeIPMIEntry 3 }

NodeIPMINetMask OBJECT-TYPE
    SYNTAX      DisplayString
    MAX-ACCESS  read-only
    STATUS      current
    DESCRIPTION "IPMI IP Netmask"
    ::= { NodeIPMIEntry 4 }

NodeIPMIGateway OBJECT-TYPE
    SYNTAX      DisplayString
    MAX-ACCESS  read-only
    STATUS      current
    DESCRIPTION "IPMI IP Gateway"
    ::= { NodeIPMIEntry 5 }

END
-- vim: set filetype=mib tabstop=4 expandtab nospell :miv --
