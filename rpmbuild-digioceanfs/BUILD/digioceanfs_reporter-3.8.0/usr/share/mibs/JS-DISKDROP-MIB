DISKDROP-MIB DEFINITIONS ::= BEGIN

IMPORTS
    MODULE-IDENTITY, OBJECT-TYPE, Integer32, Gauge32
        FROM SNMPv2-SMI
    DisplayString, TruthValue
        FROM SNMPv2-TC
    hackingExperimental
        FROM HACKING-SNMP-MIB;

DiskDropMIB MODULE-IDENTITY
        LAST-UPDATED    "201307180000Z"
        ORGANIZATION    "Hacking Networked Solutions Ltd"
        CONTACT-INFO    "Max Hacking"
        DESCRIPTION             "This MIB module defines objects for HDD SMART data."
        REVISION        "201307180000Z"
        DESCRIPTION             "Derived from DISKIO-MIB ex UCD."
    ::= { DiskDrop 1 }

DiskDrop      OBJECT IDENTIFIER ::= { hackingExperimental 8 }

DiskDropTable OBJECT-TYPE
    SYNTAX      SEQUENCE OF SsmartCtlEntry
    MAX-ACCESS  not-accessible
    STATUS      current
    DESCRIPTION "disk drop or add information."
    ::= { DiskDrop 2 }

DiskDropEntry OBJECT-TYPE
    SYNTAX      SDiskDrop
    MAX-ACCESS  not-accessible
    STATUS      current
    DESCRIPTION "Disk drop or add"
    INDEX       { DiskDropIndex }
    ::= { DiskDropTable 1 }

	SDiskDropEntry ::= SEQUENCE {
        DiskDropIndex                 Integer32,
		DiskDropCTime                 DisplayString,
        DiskDropDevName                  DisplayString,
        DiskDropDevID                  DisplayString,
        DiskDropEvent               DisplayString
}

DiskDropIndex OBJECT-TYPE
    SYNTAX      Integer32 (0..65535)
    MAX-ACCESS  read-only
    STATUS      current
    DESCRIPTION "Reference index for each observed device."
    ::= { DiskDropEntry 1 }

DiskDropCTime OBJECT-TYPE
    SYNTAX      DisplayString
    MAX-ACCESS  read-only
    STATUS      current
    DESCRIPTION "time-stamp"
    ::= { DiskDropEntry 2 }

DiskDropDevName OBJECT-TYPE
    SYNTAX      DisplayString
    MAX-ACCESS  read-only
    STATUS      current
    DESCRIPTION "disk name"
    ::= { DiskDropEntry 3 }

DiskDropDevID OBJECT-TYPE
    SYNTAX      DisplayString
    MAX-ACCESS  read-only
    STATUS      current
    DESCRIPTION "disk id"
    ::= { DiskDropEntry 4 }

DiskDropEvent OBJECT-TYPE
    SYNTAX      DisplayString
    MAX-ACCESS  read-only
    STATUS      current
    DESCRIPTION "drop or add"
    ::= { DiskDropEntry 5 }

END
