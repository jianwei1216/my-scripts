RAIDFIAL-MIB DEFINITIONS ::= BEGIN

IMPORTS
    MODULE-IDENTITY, OBJECT-TYPE, Integer32, Gauge32
        FROM SNMPv2-SMI
    DisplayString, TruthValue
        FROM SNMPv2-TC
    hackingExperimental
        FROM HACKING-SNMP-MIB;

RaidFailMIB MODULE-IDENTITY
        LAST-UPDATED    "201307180000Z"
        ORGANIZATION    "Hacking Networked Solutions Ltd"
        CONTACT-INFO    "Max Hacking"
        DESCRIPTION             "This MIB module defines objects for Fail Raid"
        REVISION        "201307180000Z"
        DESCRIPTION             "Derived from DISKIO-MIB ex UCD."
    ::= { RaidFail 1 }

RaidFail      OBJECT IDENTIFIER ::= { hackingExperimental 9 }

RaidFailTable OBJECT-TYPE
    SYNTAX      SEQUENCE OF SRaidFailEntry
    MAX-ACCESS  not-accessible
    STATUS      current
    DESCRIPTION "disk drop or add information."
    ::= { RaidFail 2 }

RaidFailEntry OBJECT-TYPE
    SYNTAX      SRaidFail
    MAX-ACCESS  not-accessible
    STATUS      current
    DESCRIPTION "Disk drop or add"
    INDEX       { RaidFailIndex }
    ::= { RaidFailTable 1 }

	SRaidFailEntry ::= SEQUENCE {
        RaidFailIndex                 Integer32,
		RaidFailCTime                  DisplayString,
        RaidFailRaidName                  DisplayString,
        RaidFailDiskName                  DisplayString,
        RaidFailEvent               DisplayString
}

RaidFailIndex OBJECT-TYPE
    SYNTAX      Integer32 (0..65535)
    MAX-ACCESS  read-only
    STATUS      current
    DESCRIPTION "Reference index for each observed device."
    ::= { RaidFailEntry 1 }

RaidFailCTime OBJECT-TYPE
    SYNTAX      DisplayString
    MAX-ACCESS  read-only
    STATUS      current
    DESCRIPTION "time-stamp"
    ::= { RaidFailEntry 2 }

RaidFailRaidName OBJECT-TYPE
    SYNTAX      DisplayString
    MAX-ACCESS  read-only
    STATUS      current
    DESCRIPTION "raid name"
    ::= { RaidFailEntry 3 }

RaidFailDiskName OBJECT-TYPE
    SYNTAX      DisplayString
    MAX-ACCESS  read-only
    STATUS      current
    DESCRIPTION "raid disk name"
    ::= { RaidFailEntry 4 }

RaidFailEvent OBJECT-TYPE
    SYNTAX      DisplayString
    MAX-ACCESS  read-only
    STATUS      current
    DESCRIPTION "raid fail type"
    ::= { RaidFailEntry 5 }

END
