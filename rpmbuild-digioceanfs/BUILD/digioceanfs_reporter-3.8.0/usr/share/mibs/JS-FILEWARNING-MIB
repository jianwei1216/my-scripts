FILEWARNING-MIB DEFINITIONS ::= BEGIN

-- imports and exports

IMPORTS
    MODULE-IDENTITY, OBJECT-TYPE, Integer32, Gauge32
        FROM SNMPv2-SMI
    DisplayString, TruthValue
        FROM SNMPv2-TC
    hackingExperimental
        FROM HACKING-SNMP-MIB;

FileWarningMIB MODULE-IDENTITY
        LAST-UPDATED    "201307180000Z"
        ORGANIZATION    "Hacking Networked Solutions Ltd"
        CONTACT-INFO    "Max Hacking"
        DESCRIPTION             "This MIB module defines objects for HDD SMART data."
        REVISION        "201307180000Z"
        DESCRIPTION             "Derived from DISKIO-MIB ex UCD."
    ::= { FileWarning 1 }

FileWarning      OBJECT IDENTIFIER ::= { hackingExperimental 7 }

FileWarningTable OBJECT-TYPE
    SYNTAX      SEQUENCE OF FileWarningEntry
    MAX-ACCESS  not-accessible
    STATUS      current
    DESCRIPTION "Table of HDD FILE information."
    ::= { FileWarning 2 }

FileWarningEntry OBJECT-TYPE
    SYNTAX      SFileWarningEntry
    MAX-ACCESS  not-accessible
    STATUS      current
    DESCRIPTION "An entry containing a device and its statistics."
    INDEX       { FileWarningIndex }
    ::= { FileWarningTable 1 }

    SFileWarningEntry ::= SEQUENCE {
        FileWarningIndex                 Integer32,
		FileWarningCTime                 DisplayString,
        FileWarningNode                  DisplayString,
        FileWarningMountPoint                  DisplayString,
		FileWarningDiskName                  DisplayString,
		FileWarningDiskID                  DisplayString,
        FileWarningEvent               DisplayString
}

FileWarningIndex OBJECT-TYPE
    SYNTAX      Integer32 (0..65535)
    MAX-ACCESS  read-only
    STATUS      current
    DESCRIPTION "Reference index for each observed device."
    ::= { FileWarningEntry 1 }

FileWarningCTime OBJECT-TYPE
    SYNTAX      DisplayString
    MAX-ACCESS  read-only
    STATUS      current
    DESCRIPTION "time-stamp"
    ::= { FileWarningEntry 2 }

FileWarningNode OBJECT-TYPE
    SYNTAX      DisplayString
    MAX-ACCESS  read-only
    STATUS      current
    DESCRIPTION "file warning node"
    ::= { FileWarningEntry 3 }

FileWarningMountPoint OBJECT-TYPE
    SYNTAX      DisplayString
    MAX-ACCESS  read-only
    STATUS      current
    DESCRIPTION "file warning mount point"
    ::= { FileWarningEntry 4 }

FileWarningDiskName OBJECT-TYPE
    SYNTAX      DisplayString
    MAX-ACCESS  read-only
    STATUS      current
    DESCRIPTION "file warning disk name"
    ::= { FileWarningEntry 5 }

FileWarningDiskID OBJECT-TYPE
    SYNTAX      DisplayString
    MAX-ACCESS  read-only
    STATUS      current
    DESCRIPTION "file warning disk id"
    ::= { FileWarningEntry 6 }

FileWarningEvent OBJECT-TYPE
    SYNTAX      DisplayString
    MAX-ACCESS  read-only
    STATUS      current
    DESCRIPTION "file warning event"
    ::= { FileWarningEntry 7 }

END
