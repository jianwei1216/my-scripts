GLOBALINFO-MIB DEFINITIONS ::= BEGIN

-- imports and exports

IMPORTS
    MODULE-IDENTITY, OBJECT-TYPE, Integer32, Gauge32
        FROM SNMPv2-SMI
    DisplayString, TruthValue
        FROM SNMPv2-TC
    hackingExperimental
        FROM HACKING-SNMP-MIB;

GlobalInfoMIB MODULE-IDENTITY
        LAST-UPDATED    "201508140000Z"
        ORGANIZATION    "Hacking Global Solutions Ltd"
        CONTACT-INFO    "Max Hacking"
        DESCRIPTION     "This MIB module defines objects for global info."
        REVISION        "201508140000Z"
        DESCRIPTION     "Derived from DISKIO-MIB ex UCD."
    ::= { GlobalInfo 1 }

GlobalInfo      OBJECT IDENTIFIER ::= { hackingExperimental 22 }

-- GlobalDomainTable

GlobalDomainTable OBJECT-TYPE
    SYNTAX      SEQUENCE OF SGlobalDomainEntry
    MAX-ACCESS  not-accessible
    STATUS      current
    DESCRIPTION "Table of domain information."
    ::= { GlobalInfo 2 }

GlobalDomainEntry OBJECT-TYPE
    SYNTAX      SGlobalDomainEntry
    MAX-ACCESS  not-accessible
    STATUS      current
    DESCRIPTION "An entry containing a domainname."
    ::= { GlobalDomainTable 1 }

    SGlobalDomainEntry ::= SEQUENCE {
        GlobalDomainName    DisplayString,
}

GlobalDomainName OBJECT-TYPE
    SYNTAX      DisplayString
    MAX-ACCESS  read-only
    STATUS      current
    DESCRIPTION "Domain Name"
    ::= { GlobalDomainEntry 1 }

END
-- vim: set filetype=mib tabstop=4 expandtab nospell :miv --
